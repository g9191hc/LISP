;;X-LINE(92cho_i)
(defun c:rx(/ os cl pt1 pt2 pt3 pt4)
   (setq os (getvar "osmode"))
   (setvar "osmode" os)
   (setq cl (getvar "clayer"))
   (prompt "\nCommand: X-line...")
   (setq pt1 (getpoint "\n Lower left corner-> int of "))
   (setq pt3 (getcorner pt1 "\n Upper right corner-> int of "))
   (setvar "osmode" os)
   (setq pt2 (list (car pt1)(cadr pt3)))
   (setq pt4 (list (car pt3)(cadr pt1)))
;   (laset "a-note-symb-lgt")
   (command "line" pt1 pt3 "")
   (command "line" pt2 pt4 "")
   (command "layer" "s" cl "")
   (setvar "osmode" os)
   (prin1)
)
