; 마지막작성일 : 230102
; 최근업데이트 : BXA삭제

; TS : 문자(Text)만 선택(Select)
; DS : 치수선(Dimension)만 선택(Select)
; BS : 블럭(Block)만 선택(Select)
; BX : 블럭(Block)만 분해(eXplode)
; HS : 해치(Hatch)만 선택(Select)
; CS : 원(Circle)만 선택(Select)
; LS : 선(Line)만 선택(Select)
; PS : 폴리라인(Polyline)만 선택(Select)
; SS : 솔리드(Solid)만 선택(Select)
; CLS : 현재(Current)레이어(Layer)와 동일한 레이어인 객체만 선택(Select)
; SLS : 선택된(Selected)객체와 동일한 레이어(Layer)인 객체만 선택(Select)
; SLCS : 선택된(Selected)객체와 동일한 레이어(Layer)이면서 동일한 컬러(Color) 객체만 선택(Select)

;;문자 잡기(text select)
(defun c:ts(/ ss)
  (princ "\n문자만 선택합니다. 객체를 선택 해 주세요.")
  (setq ss (ssget (list (cons 0 "text"))))
  (if ss
	(sssetfirst nil ss)
	(princ "선택 할 문자가 없습니다.")
  )
  (princ)
)

;;치수 잡기(dimension select)
(defun c:ds(/ ss)
  (princ "\n치수만 선택합니다. 객체를 선택 해 주세요.")
  (setq ss (ssget (list (cons 0 "dimension"))))
  (if ss
	(sssetfirst nil ss)
	(princ "선택 할 치수선이 없습니다.")
  )
  (princ)
)

;; BLOCK 잡기...(block select)
(defun c:bs(/ ss)
  (princ "\n블럭만 선택합니다. 객체를 선택 해 주세요.")
  (setq ss (ssget (list (cons 0 "INSERT"))))
  (if ss
	(sssetfirst nil ss)
	(princ "선택 할 블럭이 없습니다.")
  )
  (princ)
)

;; BLOCK 분해...(block explode)
(defun c:bx(/ ss)
  (princ "\n블럭만 선택하여 분해합니다. 객체를 선택 해 주세요.")
  (setq ss (ssget (list (cons 0 "INSERT"))))
  (if ss
	(progn
		(sssetfirst nil ss)
		(command "explode")
	)
	(princ "선택 할 블럭이 없습니다.")
  )
  (princ)
)

;;해치 잡기(hatch select)
(defun c:hs(/ ss)
  (princ "\n해치만 선택합니다. 객체를 선택 해 주세요.")
  (setq ss (ssget (list (cons 0 "hatch"))))
  (if ss
	(sssetfirst nil ss)
	(princ "선택 할 해치가 없습니다.")
  )
  (princ)
)

;; 원잡기(circle select)
(defun c:cs(/ ss)
  (princ "\n원만 선택합니다. 객체를 선택 해 주세요.")  
  (setq ss (ssget (list (cons 0 "circle"))))
  (if ss
	(sssetfirst nil ss)
	(princ "선택 할 원이 없습니다.")
  )  
  (princ)
)

;; 선 잡기(line select)
(defun c:ls(/ ss)
  (princ "\n선만 선택합니다. 객체를 선택 해 주세요.")
  (setq ss (ssget (list (cons 0 "LINE"))))
  (if ss
	(sssetfirst nil ss)
	(princ "선택 할 선이 없습니다.")
  )  
  (princ)
)

;; 폴리라인 잡기(polyline select)
(defun c:ps(/ ss)
  (princ "\n폴리선만 선택합니다. 객체를 선택 해 주세요.")
  (setq ss (ssget (list (cons 0 "LWPOLYLINE"))))
  (if ss
	(sssetfirst nil ss)
	(princ "선택 할 폴리선이 없습니다.")
  )  
  (princ)
)

;; SOLID 잡기(solid select)
(defun c:ss(/ ss)
  (princ "\n솔리드만 선택합니다. 객체를 선택 해 주세요.")
  (setq ss (ssget (list (cons 0 "solid"))))
  (if ss
	(sssetfirst nil ss)
	(princ "선택 할 솔리드가 없습니다.")
  )  
  (princ)
)

;; CLS : 현재(Current)레이어(Layer)와 동일한 레이어인 객체만 선택(Select)
(defun c:cls(/ cl ss)
  (setq cl (getvar "clayer"))
  (princ "\n현재레이어와 동일한 레이어인 객체만 선택합니다. 객체를 선택 해 주세요.")
  (setq ss (ssget (list (cons 8 cl))))
  (if ss
	(sssetfirst nil ss)
	(princ "선택 할 현재레이어를 사용하는 객체가 없습니다.")
  )  
  (princ)
)

;; 선택된(Selected)객체와 동일한 레이어(Layer)인 객체만 선택(Select)
(defun c:sls(/ ent sl ss)
  (setq ent (entget (car (entsel "\n선택하고 싶은 레이어인 객체를 선택해주세요."))))
  (setq sl (cdr (assoc 8 ent)))
  (princ (strcat "\n" sl " 레이어인 객체만 선택합니다. 객체를 선택 해 주세요."))
  (setq ss (ssget (list (cons 8 sl))))
  (if ss
	(sssetfirst nil ss)
	(princ (strcat "\n선택 할 " sl " 레이어를 사용하는 객체가 없습니다."))
  )  
  (princ)
)

;; 선택된(Selected)객체와 동일한 레이어(Layer)이면서 동일한 컬러(Color) 객체만 선택(Select)
(defun c:slcs(/ ent sl ss)
  (setq ent (entget (car (entsel "\n선택하고 싶은 레이어인 객체를 선택해주세요."))))
  (setq sl (cdr (assoc 8 ent)))
  (setq sc (cdr (assoc 62 ent)))
  (if (= sc nil)
	(progn
      (princ (strcat "\n" sl " 레이어이면서 색상이 ByLayer인 객체만 선택합니다. 객체를 선택 해 주세요."))
	  (setq ss (ssget (list (cons 8 sl) (cons 62 sc))))
	)
  )
	
  (princ (strcat "\n" sl " 레이어이면서 색상이 " sc "인 객체만 선택합니다. 객체를 선택 해 주세요."))
  (setq ss (ssget (list (cons 8 sl) (cons 62 sc))))
  (if ss
	(sssetfirst nil ss)
	(princ (strcat "\n선택 할 " sl " 레이어를 사용하는 객체가 없습니다."))
  )  
  (princ)
)
