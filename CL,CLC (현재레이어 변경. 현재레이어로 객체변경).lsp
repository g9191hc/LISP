; 현재의 레이어와 색상을 선택한 객체의 레이어와 색상으로 변경
(DEFUN C:CL (/ ENTINFO LA LC)
	(SETQ ENTINFO (ENTGET (CAR (ENTSEL))))
	(SETQ LA (CDR (ASSOC 8 ENTINFO)))
	(SETQ LC (CDR (ASSOC 62 ENTINFO)))
	(IF (= LC nil) (setq LC "BYLAYER"))
	(SETVAR "CLAYER" LA)
	(SETVAR "CECOLOR" LC)
)

; 객체의 레이어와 색상을 현재의 레이어와 색상으로 변경
(DEFUN C:CLC (/ LA LC SS ENT ENTINFO)
	(SETQ LA (GETVAR "CLAYER"))
	(SETQ LC (ATOI (GETVAR "CECOLOR")))
	(WHILE (= NIL (TYPE SS))
		(PRINC "\n현재의 레이어와 색상으로 변경할 객체를 선택 해 주세요.")
		(SETQ SS (SSGET))
	)
	(WHILE (SETQ ENT (SSNAME SS 0))
		(SETQ ENTINFO (ENTGET ENT))
		(SETQ ENTINFO (SUBST (CONS 8 LA) (ASSOC 8 ENTINFO) ENTINFO))
		(IF (ASSOC 62 ENTINFO)
			(SETQ ENTINFO (SUBST (CONS 62 LC) (ASSOC 62 ENTINFO) ENTINFO))
			(SETQ ENTINFO (APPEND ENTINFO (LIST (CONS 62 LC))))
		)
		(ENTMOD ENTINFO)
		(ssdel ent ss)
	)
)
