(defun c:test(/ dcl_id)
     (setq dcl_id (load_dialog "sample_list_box.dcl"))
     (if (not (new_dialog "sample_list_box" dcl_id))
          (exit)
     )
     (setq list_box_lst (list "Test_1" "Test_2" "Test_3"))
     (start_list "lst")
     (mapcar 'add_list list_box_lst)
     (end_list)
     (action_tile "accept" "(done_dialog)")
     (action_tile "cancel" "(done_dialog)")
     (start_dialog)
     (unload_dialog dcl_id)
)
