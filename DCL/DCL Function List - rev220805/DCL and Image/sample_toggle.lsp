(defun c:test(/ dcl_id clk grd)
     (setq dcl_id (load_dialog "sample_toggle.dcl"))
     (if (not (new_dialog "sample_toggle" dcl_id))
          (progn (princ "\nCannot find sample_toggle.dcl")(exit))
     )
     (setq grd (getvar "gridmode"))
     (set_tile "display_grid" (itoa grd))
     (action_tile "display_grid" "(setq grd $value)")
     (action_tile "accept" "(done_dialog)(setq clk T)")
     (action_tile "cancel" "(done_dialog)(setq clk nil)")
     (start_dialog)
     (unload_dialog dcl_id)
     (if clk
          (setvar "gridmode" (atoi grd))
     )
     (princ)
)
