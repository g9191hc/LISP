(defun c:test(/ dcl_id)
     (setq dcl_id (load_dialog "sample_radio_button.dcl"))
     (if (not (new_dialog "sample_radio_button" dcl_id))
          (progn (princ "\nCannot find sample_radio_button.dcl")(exit))
     )
     (action_tile "bt1" "(setvar \"cecolor\" \"1\")")
     (action_tile "bt2" "(setvar \"cecolor\" \"2\")")
     (action_tile "bt3" "(setvar \"cecolor\" \"3\")")
     (action_tile "accept" "(done_dialog)")
     (action_tile "cancel" "(done_dialog)")
     (start_dialog)
     (unload_dialog dcl_id)
)
