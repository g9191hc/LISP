(defun c:test(/ dcl_id)
     (setq dcl_id (load_dialog "sample_ok_cancel_help_errtile.dcl"))
     (if (not (new_dialog "sample_ok_cancel_help_errtile" dcl_id))
          (progn
               (princ "\nCannot find sample_ok_cancel_help_errtile.dcl")
               (exit)
          )
     )
     (action_tile "accept" "(done_dialog)")
     (action_tile "cancel" "(done_dialog)")
     (set_tile "error" "ERROR!!!")
     (start_dialog)
     (unload_dialog dcl_id)
)
