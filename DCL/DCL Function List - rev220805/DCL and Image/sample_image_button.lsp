(defun c:test(/ dcl_id)
     (setq dcl_id (load_dialog "sample_image_button.dcl"))
     (if (not (new_dialog "sample_image_button" dcl_id))
          (progn
               (princ "\nCannot find sample_image_button.dcl")
               (exit)
          )
     )
     (start_image "img")
     (slide_image 0 0 (dimx_tile "img") (dimy_tile "img") "test_slide.sld")
     (end_image)
     (action_tile "accept" "(done_dialog)")
     (action_tile "cancel" "(done_dialog)")
     (start_dialog)
     (unload_dialog dcl_id)
)
