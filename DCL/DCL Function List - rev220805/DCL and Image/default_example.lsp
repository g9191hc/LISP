(defun c:test(/ dcl_id)
     (setq dcl_id (load_dialog "default_example.dcl"))
     (if (not (new_dialog "default_example" dcl_id))
          (progn (princ "\nCannot find default_example.dcl")(exit))
     )
     (action_tile "accept" "(done_dialog)")
     (action_tile "cancel" "(done_dialog)")
     (start_dialog)
     (unload_dialog dcl_id)
)
