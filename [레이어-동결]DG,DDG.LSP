(defun C:ddg  (/ ly ce)
  (setq ce (getvar "cmdecho"))
  (setvar "cmdecho" 0)
  (command "undo" "m")
  (setq ly (getstring "\nlayers to mode thaw only? (DEF:all) "))
  (if (or (= ly "Q")(= ly "q"))
      (command "-layer" "f" "*" "u" "1*" "t" "1*" "")
      (if (or (= ly "W")(= ly "w"))
          (command "-layer" "f" "*" "u" "2*" "t" "2*" "")
          (if (or (= ly "E")(= ly "e"))
              (command "-layer" "f" "*" "u" "3*" "t" "3*" "")
              (if (or (= ly "R")(= ly "r"))
                  (command "-layer" "f" "*" "u" "4*" "t" "4*" "")
                  (if (or (= ly "T")(= ly "t"))
                      (command "-layer" "f" "*" "u" "5*" "t" "5*" "")
                      (if (or (= ly "Y")(= ly "y"))
                          (command "-layer" "f" "*" "u" "6*" "t" "6*" "")
                          (if (or (= ly "U")(= ly "u"))
                              (command "-layer" "f" "*" "u" "7*" "t" "7*" "")
                              (if (or (= ly "I")(= ly "i"))
                                  (command "-layer" "f" "*" "u" "8*" "t" "8*" "")
                                  (if (or (= ly "O")(= ly "o"))
                                      (command "-layer" "f" "*" "u" "9*" "t" "9*" "")
                                      (if (or (= ly "P")(= ly "p"))
                                          (command "-layer" "f" "*" "u" "0*" "t" "0*" "")
                                          (if (= ly "")
                                              (command "-layer" "u" "*" "t" "*" "")
                                              (command "-layer" "f" "*" "u" ly "t" ly "")
  )   )   )   )   )   )   )   )   )   )   )
  (setvar "cmdecho" ce)
  (princ)
)
(defun c:DG()
   (command "layfrz"))


(defun c:fc()
   (setvar "cmdecho" 0)
   (prompt "\n< 중심선그리기-직선 >")
   (command "osnap" "")
   (setq w-1 (entsel "\n처음선을 찍으시오.. :"))
   (setq w1 (car w-1)) (command (redraw w1 3))  
   (setq w-2 (entsel "\n다음선을 찍으시오. :"))
   (setq w2 (car w-2)) (command (redraw w1 4))  
   (setq wna1 (entget w1) xx (assoc 10 wna1)  w1p1 (cdr xx)
                          xx (assoc 11 wna1)  w1p2 (cdr xx)
         wna2 (entget w2) xx (assoc 10 wna2)  w2p1 (cdr xx)
                          xx (assoc 11 wna2)  w2p2 (cdr xx))
   (setq ang1 (angle w1p1 w1p2) d1 (distance w1p1 w1p2)
         w1p3 (polar w1p1 (+ ang1 (/ pi 2)) d1)
         w1p4 (inters w1p1 w1p3 w2p1 w2p2 nil)
           d1 (distance w1p1 w1p4) ang2 (angle w1p1 w1p4)
         l1p1 (polar w1p1 ang2 (/ d1 2)) l1p2 (polar w1p2 ang2 (/ d1 2)))
   (command "line" l1p1 l1p2 "")
   (st_os "end,mid,cen,int,per")
   (setvar "cmdecho" 1)
)
